import Part
from FreeCAD import Base;

# Create a document with the given name
document = App.newDocument('FreeCAD filler test')

# A box shape
boxShape = Part.makeBox(100, 1000, 100, Base.Vector(0, 0, 0))
# An object to display the shape
box = document.addObject('Part::Feature', 'Box')
box.Shape = boxShape

# Switch to the most convenient view
Gui.SendMsgToActiveView("ViewFit")
Gui.activeDocument().activeView().viewAxonometric()

# Re-draw the document
document.recompute()
