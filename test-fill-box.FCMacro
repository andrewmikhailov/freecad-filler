import math
import Part
from FreeCAD import Base

# Create a document with the given name
document = App.newDocument('FreeCAD filler test')

# Euclidean distance between 2 points
def euclidean_distance(first, second):
	return math.sqrt(math.pow(first.x - second.x, 2) + math.pow(first.y - second.y, 2) + math.pow(first.z - second.z, 2))

# Dimensions of a box solid shape
def shape_box_dimensions(shape):
    height = euclidean_distance(shape.Edges[6].Vertexes[0].Point, shape.Edges[6].Vertexes[1].Point)
    length = euclidean_distance(shape.Edges[7].Vertexes[0].Point, shape.Edges[7].Vertexes[1].Point)
    width = euclidean_distance(shape.Edges[8].Vertexes[0].Point, shape.Edges[8].Vertexes[1].Point)
    return width, length, height

def shape_box_fill(first, second, distance):
    # First object properties
    placementBaseFirst = first.Placement.Base
    placementRotationFirst = first.Placement.Rotation
    widthFirst, lengthFirst, heightFirst = shape_box_dimensions(first)
    # Second object properties
    widthSecond, lengthSecond, heightSecond = shape_box_dimensions(second)
    shape = None
    z = placementBaseFirst.z
    while z < placementBaseFirst.z + heightFirst:
        y = placementBaseFirst.y
        while y < placementBaseFirst.y + lengthFirst:
            x = placementBaseFirst.x
            while x < placementBaseFirst.x + widthFirst:
                if shape == None:
                    # The initial filler shape
                    shape = Part.makeBox(widthSecond, lengthSecond, heightSecond, Base.Vector(x, y, z))
                else:
                    # The on-going filler shape
                    onGoingShape = Part.makeBox(widthSecond, lengthSecond, heightSecond, Base.Vector(x, y, z))
                    shape = shape.fuse(onGoingShape)
                x = x + widthSecond + distance
            y = y + lengthSecond + distance
        z = z + heightSecond + distance
    shape.Placement.Rotation = placementRotationFirst
    return shape

# A factory to create a standard brick which was produced in the 19th century.
# Such brick has the following dimensions:
# 270 * 135 * 70 mm
class TsarBrickFactory:
    @staticmethod
    def create(location):
        return Part.makeBox(270, 135, 70, location)

# Original test box shape with placement offset and rotation
boxShape = Part.makeBox(1000, 450, 140, Base.Vector(11, 13, 17))
boxShape.rotate(Base.Vector(0, 0, 0), Base.Vector(0, 1, 0), 36)

# A fraction shape to be used for filling the original shape
fractionShape = TsarBrickFactory.create(Base.Vector(0, 0, 0))

# An object to display the final shape
box = document.addObject('Part::Feature', 'Box')
# Fill an original test shape with smaller fraction boxes by the Cartesian rule
box.Shape = shape_box_fill(boxShape, fractionShape, 3)

# Re-draw the document
document.recompute()

# Switch to the most convenient view
Gui.SendMsgToActiveView("ViewFit")
Gui.activeDocument().activeView().viewAxonometric()
